/*	This script is based on the script 'spiral-coil' by alf@cadsoft.de.
	The script was used to understand how a ULP-script works, since this is my first script and 
	I didn't feel like reading hundreds of pages of documentation.
	The stuff that I took the most inspiration (i.e. copied) from was the part below the "// *** main ***" marker (designing a dialogbox),
	the help text and sprintf to 's' and adding it to 'cmd' and write everything to eagle on exit.
	The calculations and the programming thereof was done by me, so there is probably a lot that 
	could be done better :)
	The concept for the script was orignally written in C and after sucessfull tests ported to the ULP language, 
	which has no defines, structs or pointers >:(
*/
/*
Fix wires not connecting properly between wires and arcs
Possible fix, use wire command for arcs (use the required parameters)

From the documentation (http://web.mit.edu/xavid/arch/i386_rhel4/help/100.htm):
"Do not use the WIRE command for nets, buses, and airwires. See NET, BUS and SIGNAL."

The problem might be that EAGLE uses different functions, and therefor calculations, to translate given points to an internal format for the arc and wire command.
Nobody could or wanted to help me in the EAGLE user forum and I have never heard back from the support.
Here is my post that explains the problem better, I believe: https://forums.autodesk.com/t5/eagle-forum/wires-not-connecting-with-command-line-function-calls/td-p/9889741
*/

#usage "<qt><nobr>This ULP calculates and places a wedge-shaped coil.<p>"
       "Depending from where you are starting the ULP, places pads (library) or vias (board).<p>"
       "The calculation of coils or inductivities depends on a lot of "
       "different factors, like<br>"
       " -- basic material of the board<br>"
       " -- thickness of the board<br>"
       " -- number of layers<br>"
       " -- thickness of the layers<br>"
       " -- distances between elements<br>"
       " -- tracks<br>"
       " -- copper areas / ground plains<br>"
       " -- thickness of the copper layers<br>"
       " -- track width<br>"
       " -- distances between tracks<br>"
       " -- surface of tracks (tin?)<br>"
       " -- the signal's frequency<br>"
       " -- ...<br>"
       "All these factors should be taken into consideration for the formula !<br>"
       "used below to calculate an exact value for a coil. Nevertheless it !<br>"
       "is necessary to check the result by a practical measurement. It is !<br>"
       "very difficult to generate coils with exact values this way.<br>"
       "Generally one can say that printed coils can be used in the MHz range only.<br>"
	   "<author>Author: patrick.felzer@web.de, </author></nobr></qt>";
       "<author>Based on the script 'spiral-coil' by alf@cadsoft.de,</author></nobr></qt>";

// THIS PROGRAM IS PROVIDED AS IS AND WITHOUT WARRANTY OF ANY KIND,
// EXPRESSED OR IMPLIED.

#require 4.1106

string Help = usage;

//  **************----- german description -------------***************
//   ----------------------------------------------------------------
string deHelp =
 "<qt><nobr>Dieses ULP berechnet eine Keilförmige Spule.<p>" +
 "Dieses ULP kann in der Libary ebenso wie im Board benutzt werden.<br>" +
 "Je nachdem ob Sie es von einer Library oder von einem Borad aus "
 "starten, werden Pads bzw. Vias plaziert.<br>" +
 "<br>" +
 "Die Berechnung der Windungen bzw. der Induktivitaet haengt von vielen Faktoren ab, wie z.B.:<br>" +
 " - Basismaterial<br>" +
 " - Staerke der Leiterplatte<br>" +
 " - Anzahl der Lagen<br>" +
 " - Dicke der Lagen<br>" +
 " - Abstand zu benachbarten Bauteilen, Leitungen, Kupferflaechen, Masseflaechen etc.<br>" +
 " - Dicke der Kupferbeschichtung<br>" +
 " - Breite der Leiterbahn  (unteraetzen)<br>" +
 " - Abstand zwischen den Leiterbahnen (Spiralkreise / Ätzgenauigkeit)<br>" +
 " - Oberflaeche der Leiterbahn (Verzinnt)<br>" +
 " - Signal-Frequenz<br>" +
 " - ...<br>" +
 "Um daraus einen einigermassen genauen Wert zu berechnen, muessten alle oben genannten Faktoren<br>" +
 "als Korrekturwerte in die Formael einfliessen.<br>" +
 "Was aber in jedem Fall durch entspechende Messungen nachgeprueft werden muesste.<br>" +
 "In der Praxis sind Printspulen mit genau definierten Werten und in engen Toleranzen " +
 "nur sehr schwer herzustellen.<br>" +
 "Im Allgemeinen kann man davon ausgehen, dass Printspulen nur im MHz Bereich " +
 "einigermassen Nutzbar sind.<br>" +
 "<author>Author: patrick.felzer@web.de, </author></nobr></qt>";
 "<author>Basierend auf dem Skript 'spiral-coil' von alf@cadsoft.de,</author></nobr></qt>";

if (language() == "de") Help = deHelp;

//   05.06.2002 alf@cadsoft.de
//   24.01.2005 alf@cadsoft.de
//	 19.11.2020 patrick.felzer@web.de	

// ******************************************************************

// Parameterliste  --  parameter section

//User variables
real markX = 0.0;   //Middlepoints of arc in the EAGLE coordinate system in the X-Y-System
real markY = 0.0;

real outerRadius = 85;    //in mm, Outer radius of where to start the wires
real innerRadius = 17;    //in mm, Inner radius of where to stop with the wires

int NumberOfWedgeSegments = 8;       //Number of independet arcs 360° / 8 = 45° per arc
real spacingBetweenArcs = 0.0;     // in mm

real wireWidth = 0.2;       //in mm
real wireSpacing = 0.2;     //in mm, Shortest distance between wires

//Viasize
real viaDiameter = 1.4;
real viaDrill = 0.9;
real viaBuffer = 0.5;

int innerViaConnectiontype = 2;	//0=No arc, 1=Quarter arc, 2=Half arc
int drawOnlyOneArc = 0;	//0=Draw all arcs, 1=draw only one arc

int    Layer = 1;	//1=Top Layer
//End of user variables

int PRECISION = 3;	//Determines to what decimal place numbers will be rounded
int WIREBEND = 2;  //see http://web.mit.edu/xavid/arch/i386_rhel4/help/86.htm
string Shape = "ROUND";         // Pad/Via-Form nicht veraendern

string cmd = "";
string s;
string solderpoint;

string nameForWire;
string turnDirection;

real spacingForFirstWire = 0.0;
int placeViaInsideCoils = 0;

//Global constants
real RADTODEGREE = (180/PI);
real DEGREETORAD = (PI/180);


int DEBUG = 0;
int useXYCoordiantes = 0;
int useRounding = 0;
int windings = 0;


real roundUp(real roundMe){
	if(useRounding){
		int precisionDenominator=1;
		for(int k=0; k<PRECISION; ++k)
			precisionDenominator = precisionDenominator*10;
			
		roundMe = roundMe*precisionDenominator;
		roundMe = ceil(roundMe);
		return roundMe/precisionDenominator;
	} 
	return roundMe;
}

real roundDown(real roundMe){
	if(useRounding){
		int precisionDenominator=1;
		for(int l=0; l<PRECISION; ++l)
			precisionDenominator = precisionDenominator*10;
		
		roundMe = roundMe*precisionDenominator;
		roundMe = floor(roundMe);
		return roundMe/precisionDenominator;
	} 
	return roundMe;
}

real polarToX(real r, real phi){
    return r*cos(phi*DEGREETORAD);
}

real polarToY(real r, real phi){
    return r*sin(phi*DEGREETORAD);
}

real xyToPolarR(real x, real y){
    return sqrt( pow(x,2)+pow(y,2) );
}

real xyToPolarPhi(real x, real y){
    return RADTODEGREE*atan(y/x);
}


void printLine(string nameForWire, real rStart, real phiStart, real rEnd, real phiEnd){
	if(useXYCoordiantes){
		real tempStartX=0,tempStartY=0;
		real tempEndX=0,tempEndY=0;
		tempStartX=polarToX(rStart, phiStart);
		tempStartY=polarToY(rStart, phiStart);
		tempEndX=polarToX(rEnd, phiEnd);
		tempEndY=polarToY(rEnd, phiEnd);
		sprintf( s, "WIRE '%s' %.*f ROUND (%.*f %.*f) (%.*f %.*f);\n", nameForWire, PRECISION, wireWidth, PRECISION, tempStartX, PRECISION, tempStartY, PRECISION, tempEndX, PRECISION, tempEndY);
		cmd += s;
		++windings;
	} else {
		sprintf( s, "WIRE '%s' %.*f ROUND (P%.*f %.*f) (P%.*f %.*f);\n", nameForWire, PRECISION, wireWidth, PRECISION, rStart, PRECISION, phiStart, PRECISION, rEnd, PRECISION, phiEnd);
		cmd += s;
		++windings;
	}
}

void printArc(string nameForWire, string turnDirection, real arcR, real arcPhiStart, real oppositeSideOfArcPhiStart, real arcPhiEnd){
    if(useXYCoordiantes){
		real tempStartX=0,tempStartY=0;
		real tempEndX=0,tempEndY=0;
		real tempOppositeX=0, tempOppositeY=0;
		tempStartX=polarToX(arcR, arcPhiStart);
		tempStartY=polarToY(arcR, arcPhiStart);
		tempEndX=polarToX(arcR, arcPhiEnd);
		tempEndY=polarToY(arcR, arcPhiEnd);
		tempOppositeX=polarToX(arcR, oppositeSideOfArcPhiStart);
		tempOppositeY=polarToY(arcR, oppositeSideOfArcPhiStart);
		sprintf( s, "arc '%s' %s %.*f (%.*f %.*f) (%.*f %.*f) (%.*f %.*f);\n", nameForWire, turnDirection, PRECISION, wireWidth, PRECISION, tempStartX, PRECISION, tempStartY, PRECISION, tempOppositeX, PRECISION, tempOppositeY, PRECISION, tempEndX, PRECISION, tempEndY);
		cmd += s;	
	} else {
		sprintf( s, "arc '%s' %s %.*f (P%.*f %.*f) (P%.*f %.*f) (P%.*f %.*f);\n", nameForWire, turnDirection, PRECISION, wireWidth, PRECISION, arcR, PRECISION, arcPhiStart, PRECISION, arcR, PRECISION, oppositeSideOfArcPhiStart, PRECISION, arcR, PRECISION, arcPhiEnd);
		cmd += s;
	}
}

void placeVia(string nameForWire, real R, real phi){
	if(useXYCoordiantes){
		real tempX=0,tempY=0;
		tempX=polarToX(R, phi);
		tempY=polarToY(R, phi);
		sprintf( s, "%s '%s' ROUND 1-2 (%f %f);\n", solderpoint, nameForWire, tempX, tempY);
		cmd += s;
	} else {
		sprintf( s, "%s '%s' ROUND 1-2 (P%f %f);\n", solderpoint, nameForWire, R, phi);
		cmd += s;
	}
}

void exitProgramFault(void){
	dlgMessageBox("Something went wrong! :(", "Fine", "Not Fine");
	exit("");
}

void exitProgram(void){
	sprintf(s,  "Change Layer tPlace;\n");

	sprintf(s,  "window (%6.3f %6.3f);\n", markX, markY);
	cmd += s;
	sprintf(s,  "SET WIRE_BEND @;\n");
	cmd += s;
	
	string messageWindings = "";
	if(!drawOnlyOneArc){
		windings = windings/NumberOfWedgeSegments;
	}
	sprintf( messageWindings, "Windings: %d", windings/2 );
	
	int varCancel = dlgMessageBox(messageWindings, "Ok", "Cancel");
	
	if(varCancel == 1){
		exit("");
	}else{
		exit(cmd);
	}
}

void doit(void) {
	// Calculations for whatever
	real rStart, rEnd;
    real phiStart[];
	real phiEnd[];
	real phiOpposite[];
    real horizontalSpacing = 0, verticalSpacing = 0;

    real spaceingForWireOrVia = 0;
    real spacingViaWireArcsegmentInDegree = 0;
    
    real phiKreisbogen = 0;
    real kreisSehne = 0;
	
	real VIASPACINGDIAMETER = (viaDiameter+(viaBuffer*2));
	real WIREMIDDLESPACING = (wireSpacing+wireWidth);
	real ARCSEGMENTSINDEGREE = (360.0/NumberOfWedgeSegments);
	real ARCSEGMENTSINRAD = ((2*PI)/NumberOfWedgeSegments);
    
    int completedTurns = 0;
    int skipInnerArc = 0;
    
    //Set Arrays to zero
    for(int m=0;m<NumberOfWedgeSegments;++m){
        phiStart[m]=0;
        phiEnd[m]=0;
        phiOpposite[m]=0;
    }
    
	if(spacingBetweenArcs <= wireSpacing)
		spacingBetweenArcs = wireSpacing/2;
	
    if(VIASPACINGDIAMETER>=wireWidth)
        spacingForFirstWire = VIASPACINGDIAMETER/2.0;
    else
        spacingForFirstWire =  wireWidth/2.0;
	
	//Init
	sprintf(s,  "GRID mm;\n");
	cmd += s;
	sprintf(s,  "change diameter %4.2f;\n", viaDiameter);
	cmd += s;
	sprintf(s,  "change shape %s;\n", Shape);
	cmd += s;
	sprintf(s,  "change drill %4.2f;\n", viaDrill);
	cmd += s;
	sprintf(s,  "change width %4.3f;\n", wireWidth);
	cmd += s;
	sprintf(s,  "set wire_bend %d;\n", WIREBEND);
	cmd += s;
	sprintf(s,  "change layer %d;\n", Layer);
	cmd += s;

	//Calc and draw arcs
	for(int i = 0; ;++i){
		if(i!=0 && i%4==0)  // +1 after a full turn of the coil was drawn
			++completedTurns;
			
		switch(i%4){
			case 0: //***************************Outer arc***************************
				if(i==0){   //First outer arc (to mind the Via)
					rStart = outerRadius - spacingForFirstWire;
					rEnd = rStart;    //R is the same through the arc
					spacingViaWireArcsegmentInDegree = asin( (spacingBetweenArcs+(spacingForFirstWire)) / rStart )*RADTODEGREE;   //Get degree offset due to spacing
					phiStart[0] = ARCSEGMENTSINDEGREE - spacingViaWireArcsegmentInDegree;   //Subtract from full arc to get clockwise arc
					phiStart[0] = roundDown(phiStart[0]); //Round down to avoid conflict with spacing
				}else{  //Following outer arcs
					rStart = rEnd;
					rEnd = rStart; //R is the same through the arc
					phiStart[0] = phiEnd[0];
				}
				
				//Calc polar coordiantes for the opposite side of phiStart (Sets radius of arc, R is same as start and end)
				phiOpposite[0] = phiStart[0] - 180;
				
				//Calc Polar End-Phi-Coordinate with spacing in mind
				phiEnd[0] = asin( (spacingBetweenArcs+(wireWidth/2)+(completedTurns*WIREMIDDLESPACING)) / rStart ) * RADTODEGREE;  //Only wire is considered, since there is no via here
				phiEnd[0] = roundUp(phiEnd[0]); //Round up to avoid conflict with spacing
				
				//No more space, place via inside coils and exit program
				if(placeViaInsideCoils){
					for(int j=0; j<NumberOfWedgeSegments; ++j){
						phiStart[j] = phiStart[0]+(j*ARCSEGMENTSINDEGREE);
						phiOpposite[j] = phiStart[j] - 180;
						
						phiEnd[j] = phiEnd[0]+(j*ARCSEGMENTSINDEGREE);
						sprintf(nameForWire,"Wedge_%d", j+1);
						
							
						if( !(drawOnlyOneArc && j ) ){
							placeVia(nameForWire, rStart-(VIASPACINGDIAMETER/2), (ARCSEGMENTSINDEGREE/2)+(j*ARCSEGMENTSINDEGREE) );
							
							switch(innerViaConnectiontype){
								case 0:	//No arc
									printLine(nameForWire, rStart, phiStart[j], rStart-(VIASPACINGDIAMETER/2), (ARCSEGMENTSINDEGREE/2)+(j*ARCSEGMENTSINDEGREE) );
									break;
								case 1:	//Quarter arc
									real phiOffsetQuarterArc = (phiStart[0]-(ARCSEGMENTSINDEGREE/2))/2;
									real phiQuarterArc = (ARCSEGMENTSINDEGREE/2)+(j*ARCSEGMENTSINDEGREE)+phiOffsetQuarterArc;
									
									printArc(nameForWire, "CW", rStart, phiStart[j], phiOpposite[j], phiQuarterArc);
									printLine(nameForWire, rStart, phiQuarterArc, rStart-(VIASPACINGDIAMETER/2), (ARCSEGMENTSINDEGREE/2)+(j*ARCSEGMENTSINDEGREE));
									break;
								case 2:	//Half arc
									printArc(nameForWire, "CW", rStart, phiStart[j], phiOpposite[j], (ARCSEGMENTSINDEGREE/2)+(j*ARCSEGMENTSINDEGREE));
									printLine(nameForWire, rStart, (ARCSEGMENTSINDEGREE/2)+(j*ARCSEGMENTSINDEGREE), rStart-(VIASPACINGDIAMETER/2), (ARCSEGMENTSINDEGREE/2)+(j*ARCSEGMENTSINDEGREE));
									break;
							}
						}
					}
					exitProgram();
				}
				
				//Calc values for other NumberOfWedgeSegments and print them
				for(int n=0; n<NumberOfWedgeSegments; ++n){
					if( !(drawOnlyOneArc && n) ){
						phiStart[n] = phiStart[0]+(n*ARCSEGMENTSINDEGREE);
						phiOpposite[n] = phiStart[n] - 180;
						
						phiEnd[n] = phiEnd[0]+(n*ARCSEGMENTSINDEGREE);
				
						sprintf(nameForWire,"Wedge_%d", n+1);

						if(i==0)
							placeVia(nameForWire, rStart, phiStart[n]);
						printArc(nameForWire, "CW", rStart, phiStart[n], phiOpposite[n], phiEnd[n]);
					}
				}
				break;
			case 1: //***************************Right wire***************************
				rStart = rEnd;
				for(int o=0; o<NumberOfWedgeSegments; ++o)
					phiStart[o] = phiEnd[o];
				
				rEnd = innerRadius + (wireWidth/2) + (completedTurns*WIREMIDDLESPACING);
				phiEnd[0] = asin( (spacingBetweenArcs+(wireWidth/2)+(completedTurns*WIREMIDDLESPACING)) / rEnd ) * RADTODEGREE;
				phiEnd[0] = roundUp(phiEnd[0]);
				
				// Check for the need of an inner arc
				if(skipInnerArc || phiEnd[0] >= ARCSEGMENTSINDEGREE/2){ // inner arc is not needed, set variables and correct phiEnd
					skipInnerArc = 1;    //Skips the inner arc since wires can connect without it
					phiEnd[0] = ARCSEGMENTSINDEGREE/2;
					
					rEnd = (spacingBetweenArcs+(wireWidth/2)+(completedTurns*WIREMIDDLESPACING))/sin( ARCSEGMENTSINRAD/2 );
				}
				
				
				//Check spacing inside coils (for next iteration) for via-placement
				
				//Functions for conversion polar to xy and vice versa
				//void polarToXy(real r, real phi, real *x, real *y);
				//void xyToPolar(real x, real y, real *r, real *phi);
				
				// Added offsets for wires are to calc wheter or not the via (+buffer)
				// will intersect the wires during the next iteration of drawing wires
				
				real rViaCenter = rStart-(VIASPACINGDIAMETER/2)-WIREMIDDLESPACING-(wireWidth/2);
				real phiViaCenter = ARCSEGMENTSINDEGREE/2;
				real xViaCenter = 0;
				real yViaCenter = 0;
				real xStartRightWire = 0;
				real yStartRightWire = 0;
				real xEndRightWire = 0;
				real yEndRightWire = 0;
				
				//Get xy-for Via center and start of wire right
				xViaCenter = polarToX(rViaCenter, phiViaCenter);
				yViaCenter = polarToY(rViaCenter, phiViaCenter);
				
				xStartRightWire = polarToX(rStart, phiStart[0]);
				yStartRightWire = polarToY(rStart, phiStart[0]);
				
				// Check vertical clearance for the via
				if( yViaCenter-(VIASPACINGDIAMETER/2) <= yStartRightWire+WIREMIDDLESPACING+(wireWidth/2) ){   
					placeViaInsideCoils = 1;
				}
				
				//Check radial clearance for the via
				if( rEnd+WIREMIDDLESPACING+(wireWidth/2) >= rViaCenter-(VIASPACINGDIAMETER/2) ){
					placeViaInsideCoils = 1;
				}
				
				//Calc values for other NumberOfWedgeSegments and print them
				for(int p=0; p<NumberOfWedgeSegments; ++p){
					if( !(drawOnlyOneArc && p) ){
						phiEnd[p] = phiEnd[0]+(p*ARCSEGMENTSINDEGREE);
			
						sprintf(nameForWire,"Wedge_%d", p+1);
						
						printLine(nameForWire, rStart, phiStart[p], rEnd, phiEnd[p]);
					}
				}
				
				break;
			case 2: //***************************Inner arc***************************
				if(skipInnerArc) //inner arc isn't needed, skip this case.
					break;
					
				//Calc and draw inner arc
				rStart = rEnd;
				for(int t=0; t<NumberOfWedgeSegments; ++t)
					phiStart[t] = phiEnd[t];
					
				//Calc Polar End-Phi-Coordinate with spacing in mind
				phiEnd[0] = asin( (spacingBetweenArcs+(wireWidth/2)+(completedTurns*WIREMIDDLESPACING)) / rStart ) * RADTODEGREE;  //Only wire is considered, since there is no via here
				phiEnd[0] = roundDown(ARCSEGMENTSINDEGREE-phiEnd[0]); //Round up to avoid conflict with spacing
				
				//Calc values for other NumberOfWedgeSegments and print them
				for(int q=0; q<NumberOfWedgeSegments; ++q){
					if( !(drawOnlyOneArc && q) ){
						phiOpposite[q] = phiStart[q] - 180;
						
						phiEnd[q] = phiEnd[0]+(q*ARCSEGMENTSINDEGREE);
				
						sprintf(nameForWire,"Wedge_%d", q+1);
						
						printArc(nameForWire, "CCW", rStart, phiStart[q], phiOpposite[q], phiEnd[q]);
					}
				}
					
				break;
			case 3: //***************************Left wire***************************
				rStart = rEnd;
				for(int r=0; r<NumberOfWedgeSegments; ++r)
					phiStart[r] = phiEnd[r];
				
				rEnd = outerRadius - ((spacingForFirstWire*2)+wireSpacing) - (completedTurns*WIREMIDDLESPACING) - (wireWidth/2);
				
				phiEnd[0] = asin( (spacingBetweenArcs+(wireWidth/2)+(completedTurns*WIREMIDDLESPACING)) / rEnd ) * RADTODEGREE;
				phiEnd[0] = roundUp(ARCSEGMENTSINDEGREE-phiEnd[0]);
				
				//Calc values for other NumberOfWedgeSegments and print them
				for(int s=0; s<NumberOfWedgeSegments; ++s){
					if( !(drawOnlyOneArc && s) ){
						phiEnd[s] = phiEnd[0]+(s*ARCSEGMENTSINDEGREE);
				
						sprintf(nameForWire,"Wedge_%d", s+1);

						printLine(nameForWire, rStart, phiStart[s], rEnd, phiEnd[s]);
					}
				}
				break;
			default: 
				exitProgramFault();
		}      /* Ende switch */
	}
}


// *** main ***
if (board) board(B) { solderpoint = "VIA"; };
if (library) library(L) {solderpoint = "PAD"; };

string ulp_path = filedir(argv[0]);					//No idea
string Spiral_H = "<img src=spiral-coil-ulp.bmp>";	//No idea

//Dialogbox
dlgDialog("Wedge shaped coils") {
	dlgHBoxLayout {
		dlgVBoxLayout {
			dlgGridLayout {
				dlgCell(1, 1) dlgLabel("Number of wedges");
				dlgCell(1, 2) dlgIntEdit(NumberOfWedgeSegments, 2, 100);
				dlgCell(2, 1) dlgLabel("Outer radius of wedge");
				dlgCell(2, 2) dlgRealEdit(outerRadius);
				dlgCell(3, 1) dlgLabel("Inner radius of wedge");
				dlgCell(3, 2) dlgRealEdit(innerRadius);
				dlgCell(4, 1) dlgLabel("Spacing between wedges");
				dlgCell(4, 2) dlgRealEdit(spacingBetweenArcs);
			}
			dlgLabel("<hr>");
			dlgGroup("Via/Pad connection inside of the wedge"){
				dlgRadioButton("Straight connection (Might cross wires)", innerViaConnectiontype);
				dlgRadioButton("Draw a quarter arc", innerViaConnectiontype);
				dlgRadioButton("Draw a half arc", innerViaConnectiontype);
			}
			//dlgLabel("<hr>");
			//dlgGroup(""){
			//	dlgRadioButton("Draw all wedges", drawOnlyOneArc);
			//	dlgRadioButton("Draw one wedge", drawOnlyOneArc);
			//}
			if(DEBUG){
				dlgLabel("<hr>");
				dlgGroup("Output coordinates in"){
					dlgRadioButton("Polar", useXYCoordiantes);
					dlgRadioButton("X-Y", useXYCoordiantes);
				}
				dlgLabel("<hr>");
				dlgGridLayout {
					dlgCell(1, 1) dlgLabel("Decimal places:");
					dlgCell(1, 2) dlgIntEdit(PRECISION, 0, 100);
				}
				dlgLabel("<hr>");
				dlgGroup("Use rounding"){
					dlgRadioButton("No", useXYCoordiantes);
					dlgRadioButton("Yes", useXYCoordiantes);
				}
			}
		}
		dlgVBoxLayout {
			dlgGridLayout {
				dlgCell(1, 1) dlgLabel("Wire &width 'w'");                // track width
				dlgCell(1, 2) dlgRealEdit(wireWidth, 0.01, 25.0);
				dlgCell(2, 1) dlgLabel("Wire &distance 'd'");             // min. distance between tracks
				dlgCell(2, 2) dlgRealEdit(wireSpacing, .01, 25.0);
				dlgCell(3, 1) dlgLabel("Via/Pad di&ameter");              // pad/via diameter
				dlgCell(3, 2) dlgRealEdit(viaDiameter, 0.1, 10.0);
				dlgCell(4, 1) dlgLabel("Via/Pad d&rill");                 // drill diameter
				dlgCell(4, 2) dlgRealEdit(viaDrill, .1, 10.0);
				dlgCell(5, 1) dlgLabel("Buffer around Via/Pad"); // Buffer around Via/Pad 
				dlgCell(5, 2) dlgRealEdit(viaBuffer);
				dlgCell(6, 1) dlgLabel("&Layer");                         // Layer number
				dlgCell(6, 2) dlgIntEdit(Layer, 1, 255);
				//dlgCell(7, 1) dlgLabel("<hr>");							  // Seperation Lines
				//dlgCell(7, 2) dlgLabel("<hr>");
				//dlgCell(8, 1) dlgLabel("Not yet implemented!");
				//dlgCell(9, 1) dlgLabel("Offset &X");                      // place with offset X
				//dlgCell(9, 2) dlgRealEdit( markX );
				//dlgCell(10, 1) dlgLabel("Offset &Y");                      // place with offset Y
				//dlgCell(10, 2) dlgRealEdit( markY );
			}
			dlgLabel("<hr>");
			dlgGroup(""){
				dlgRadioButton("Draw all wedges", drawOnlyOneArc);
				dlgRadioButton("Draw one wedge", drawOnlyOneArc);
			}
			dlgStretch(1);
		}
	}
	dlgLabel("<qt>All measures in <b>mm</b></qt>");
	dlgHBoxLayout {
	dlgPushButton("+&OK")     { dlgAccept(); doit(); }
	dlgPushButton("-&Cancel") { dlgReject(); exit(0); }
	dlgStretch(1);
	dlgPushButton("&Help") dlgMessageBox(Help, "Ok");
	}
};
